ELTEX-MES-IP DEFINITIONS ::= BEGIN

-- Title:      ELTEX MES IP Private Extension
-- Version:    1.1
-- Date:       12 Dec 2017

IMPORTS
    eltMes                                                  FROM ELTEX-MES
    rlInetRoutingDistanceEntry                              FROM RADLAN-IPv6
    OBJECT-TYPE                                             FROM SNMPv2-SMI
    TruthValue                                              FROM SNMPv2-TC
    ifIndex                                                 FROM IF-MIB;


eltMesIpSpec MODULE-IDENTITY
       LAST-UPDATED "201402120000Z"
       ORGANIZATION "Eltex Enterprise Co, Ltd."
       CONTACT-INFO
            "www.eltex.nsk.ru"
       DESCRIPTION
            "The private MIB module definition for IP MIB."
       REVISION "200606220000Z"
       DESCRIPTION
            "Initial version of this MIB."
       ::= { eltMes 91 }


eltMesOspf OBJECT IDENTIFIER ::=  { eltMesIpSpec 1 }
-- see eltIpRouter.mib

eltMesArpSpec OBJECT IDENTIFIER ::=  { eltMesIpSpec 3 }
-- see eltArpInterfaceTable.mib

--
-- eltMesInetRouting
--

eltMesInetRouting OBJECT IDENTIFIER ::=  { eltMesIpSpec 4 }

eltInetRoutingDistanceTable OBJECT-TYPE
    SYNTAX      SEQUENCE OF EltInetRoutingDistanceEntry
    MAX-ACCESS  not-accessible
    STATUS      current
    DESCRIPTION "This table defines administrative distances for
                 different protocol routes that are inserted into
                 the routing table.

                 The table augments rlInetRoutingDistanceTable."
    ::= { eltMesInetRouting 1 }

eltInetRoutingDistanceEntry OBJECT-TYPE
    SYNTAX      EltInetRoutingDistanceEntry
    MAX-ACCESS  not-accessible
    STATUS      current
    DESCRIPTION "A set of distances per inet address type."
    AUGMENTS    { rlInetRoutingDistanceEntry }
    ::= { eltInetRoutingDistanceTable 1 }

EltInetRoutingDistanceEntry ::= SEQUENCE {
    eltInetRoutingDistanceBgpInternal           INTEGER,
    eltInetRoutingDistanceBgpExternal           INTEGER
}

eltInetRoutingDistanceBgpInternal OBJECT-TYPE
    SYNTAX      INTEGER  (0..255)
    MAX-ACCESS  read-write
    STATUS      current
    DESCRIPTION "The administrative distance used for internal BGP routes."
    ::= { eltInetRoutingDistanceEntry 1 }


eltInetRoutingDistanceBgpExternal OBJECT-TYPE
    SYNTAX      INTEGER  (0..255)
    MAX-ACCESS  read-write
    STATUS      current
    DESCRIPTION "The administrative distance used for external BGP routes."
    ::= { eltInetRoutingDistanceEntry 2 }

END
