ELTEX-MES-SYSLOG-MIB DEFINITIONS ::= BEGIN

-- Title:      ELTEX MES SYSLOG Private MIB
-- Version:    2.0
-- Date:       11 May 2016
--
-- 03-Aug-2015 Added eltMesSyslogEvents
-- 11-May-2016 Added eltSyslogUserCmdEnable

IMPORTS
    eltMes                                  FROM ELTEX-MES
    OBJECT-TYPE, IpAddress, Unsigned32,Counter32,
    MODULE-IDENTITY                         FROM SNMPv2-SMI
    EltCpuRateLimiterTrafficType            FROM ELTEX-MES-SWITCH-RATE-LIMITER-MIB
    DisplayString, TEXTUAL-CONVENTION,
    TruthValue, RowStatus                   FROM SNMPv2-TC;

eltMesSyslog MODULE-IDENTITY
          LAST-UPDATED "201605110000Z"
          ORGANIZATION "Eltex Ltd."
          CONTACT-INFO
                  "eltex.nsk.ru"
          DESCRIPTION
                  "The private MIB module definition for SYSLOG services in Eltex devices."
          ::= { eltMes 10 }

eltSyslogCpuRateLimiterTable OBJECT-TYPE
    SYNTAX          SEQUENCE OF EltSyslogCpuRateLimiterEntry
    MAX-ACCESS      not-accessible
    STATUS          current
    DESCRIPTION        "Enable/disable logging per CPU rate limitter."
    ::= { eltMesSyslog 1 }

eltSyslogCpuRateLimiterEntry OBJECT-TYPE
    SYNTAX          EltSyslogCpuRateLimiterEntry
    MAX-ACCESS      not-accessible
    STATUS          current
    DESCRIPTION        "An entry containing enable/disable logging settings per CPU rate limitter."
    INDEX           { eltSyslogCpuRateLimiterIndex }
    ::= { eltSyslogCpuRateLimiterTable 1 }

EltSyslogCpuRateLimiterEntry ::= SEQUENCE {
        eltSyslogCpuRateLimiterIndex       EltCpuRateLimiterTrafficType,
        eltSyslogCpuRateLimiterEnabled     TruthValue
}

eltSyslogCpuRateLimiterIndex OBJECT-TYPE
    SYNTAX          EltCpuRateLimiterTrafficType
    MAX-ACCESS      read-only
    STATUS          current
    DESCRIPTION        "Traffic type"
    ::= { eltSyslogCpuRateLimiterEntry 1 }

eltSyslogCpuRateLimiterEnabled OBJECT-TYPE
    SYNTAX          TruthValue
    MAX-ACCESS      read-write
    STATUS          current
    DESCRIPTION        "Enable logging of rate-limiter events"
    ::= { eltSyslogCpuRateLimiterEntry 2 }

--
-- eltMesSyslogEvents
--

eltMesSyslogEvents  OBJECT IDENTIFIER
    ::= { eltMesSyslog 2 }

--
-- eltSyslogEventsStpTable
--

eltSyslogEventsStpTable OBJECT-TYPE
    SYNTAX          SEQUENCE OF EltSyslogEventsStpEntry
    MAX-ACCESS      read-write
    STATUS          current
    DESCRIPTION        "Enable/disable logging of STP events."
    ::= { eltMesSyslogEvents 2 }

EltSyslogEventsStpEventType ::= TEXTUAL-CONVENTION
    STATUS current
    DESCRIPTION    "Types of STP events."
    SYNTAX INTEGER {
        eltSyslogEventsStpEventStateChange(1),
        eltSyslogEventsStpEventTopologyChange(2),
        eltSyslogEventsStpEventRootBridgeChange(3)
}

EltSyslogEventsStpEntry ::= SEQUENCE {
	eltSyslogEventsStpEventIndex  		EltSyslogEventsStpEventType,
	eltSyslogEventsStpEventEnabled      TruthValue
}

eltSyslogEventsStpEntry OBJECT-TYPE
    SYNTAX          EltSyslogEventsStpEntry
    MAX-ACCESS      read-write
    STATUS          current
    DESCRIPTION        "An entry containing enable/disable logging of STP events."
    INDEX           { eltSyslogEventsStpEventIndex }
    ::= { eltSyslogEventsStpTable 1 }

eltSyslogEventsStpEventIndex OBJECT-TYPE
	SYNTAX			EltSyslogEventsStpEventType
    MAX-ACCESS		read-write
    STATUS			current
    DESCRIPTION			"Specify the index of STP event."
    ::= { eltSyslogEventsStpEntry 1 }

eltSyslogEventsStpEventEnabled OBJECT-TYPE
	SYNTAX			TruthValue
    MAX-ACCESS		read-write
    STATUS			current
    DESCRIPTION			"Enable logging of STP event."
    ::= { eltSyslogEventsStpEntry 2 }


eltSyslogUserCmdEnable OBJECT-TYPE
    SYNTAX  TruthValue
    MAX-ACCESS  read-write
    STATUS  current
    DESCRIPTION
        "User commands enter enable for syslog flash, syslog cache and syslog UDP.
         When set to true, generating syslog entry for user commands entered."
    DEFVAL  { false }
    ::= { eltMesSyslog 3 }
    
END
